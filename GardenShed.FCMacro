import FreeCAD, Draft, Arch, FreeCADGui, math, Part

shed_width = 3840
shed_depth = 2500
roof_overhang = 250
beam_thickness = 80
rafter_height = 120
height_front = 2200
height_back = 2000
door_width = 1500
door_height = 2000
beam_overlap = 15
support_height = 300
support_angle = 70
stud_max_distance = 1000
rafter_max_distance = 1000
batten_max_distance = 500
batten_height = 30
batten_thickness = 50
facade_board_thickness = 19
facade_board_width = 121-8
door_extra_gap = beam_thickness / 2
foundation_height = 750
foundation_diameter = 153
foundation_gap = 15
anchor_thickness = 5
anchor_width = 60
anchor_height = 600
document_name = 'GardenShed'

def init_doc():
  if FreeCAD.ActiveDocument and FreeCAD.ActiveDocument.Label == document_name:
    doc = FreeCAD.ActiveDocument
    for obj in doc.Objects:
      doc.removeObject(obj.Name)
    
    return doc
  else:
    doc = FreeCAD.newDocument()
    doc.Label = document_name
    return doc

def bottom(part):
  return part.Placement.Base.z

def top(part):
  return part.Placement.Base.z + part.Height.Value

def front(part):
  return part.Placement.Base.y

def back(part):
  return part.Placement.Base.y + part.Width.Value

def left(part):
  return part.Placement.Base.x

def right(part):
  return part.Placement.Base.x + part.Length.Value

def makeCuboid(name, x, y, z):
  box = doc.addObject("Part::Box", name)
  box.Length = x
  box.Width = y
  box.Height = z
  box.Placement = FreeCAD.Placement(FreeCAD.Vector(x/-2, y/-2, z/-2), FreeCAD.Rotation())
  return box

def makeStud(name, height):
  return makeCuboid(name, beam_thickness, beam_thickness, height)

def moveLeftFrontBottom(part, x, y, z):
  new_x = part.Length.Value / 2 + x
  new_y = part.Width.Value / 2 + y
  new_z = part.Height.Value / 2 + z
  Draft.move(part, FreeCAD.Vector(new_x, new_y, new_z))

def moveLeftFrontTop(part, x, y, z):
  new_x = part.Length.Value / 2 + x
  new_y = part.Width.Value / 2 + y
  new_z = z - (part.Height.Value / 2)
  Draft.move(part, FreeCAD.Vector(new_x, new_y, new_z))

def makeInnerStuds(name, height, from_stud, to_stud, direction):
  if direction == "front_to_back":
    distance = front(to_stud) - back(from_stud)
  elif direction == "left_to_right":
    distance = left(to_stud) - right(from_stud)
  else:
    raise ValueError("unknown direction: " + direction)

  inner_space_count = math.ceil(distance/stud_max_distance)
  inner_stud_count = inner_space_count - 1
  inner_stud_space = (distance - (inner_stud_count * beam_thickness)) / inner_space_count

  inner_studs = [] 

  for i in range(1, inner_space_count):
    offset = (i * inner_stud_space) + ((i - 1) * beam_thickness)

    if direction == "front_to_back":
      x = left(from_stud)
      y = back(from_stud) + offset
    elif direction == "left_to_right":
      x = right(from_stud) + offset
      y = front(from_stud)
    else:
      raise ValueError("unknown direction: " + direction)

    stud = makeStud('InnerStud' + name + str(i), height)
    moveLeftFrontBottom(stud, x, y, 0)
    
    inner_studs.append(stud)
  
  return inner_studs

def makeSupportBeam(name, at_stud, direction):
  support_beam_size = (at_stud.Height.Value - support_height - beam_overlap) / math.sin(math.radians(support_angle))
  support_beam = makeStud('Support' + name, support_beam_size)
  moveLeftFrontBottom(support_beam, left(at_stud), front(at_stud), bottom(at_stud) + support_height)

  if direction == 'left':
    angle = -90 + support_angle
    axis = FreeCAD.Vector(0, 1, 0) 
    center_x = left(support_beam)
    center_y = front(support_beam)
  elif direction == 'right':
    angle = 90 - support_angle
    axis = FreeCAD.Vector(0, 1, 0) 
    center_x = right(support_beam)
    center_y = front(support_beam)
  elif direction == 'front':
    angle = 90 - support_angle
    axis = FreeCAD.Vector(1, 0, 0) 
    center_x = left(support_beam)
    center_y = front(support_beam)
  elif direction == 'back':
    angle = -90 + support_angle
    axis = FreeCAD.Vector(1, 0, 0) 
    center_x = left(support_beam)
    center_y = back(support_beam) 

  Draft.rotate(support_beam, angle=angle, axis=axis, center=FreeCAD.Vector(center_x, center_y, bottom(support_beam)))
  return support_beam

def calculate_roof_angle(chord_front, chord_back):
  a = top(chord_front) - top(chord_back)
  b = front(chord_back) - front(chord_front)
  c = math.sqrt(math.pow(a, 2) + math.pow(b, 2))
  return math.degrees(math.asin(a/c))


def calculate_rafter_length(rafter_angle, chord_front, chord_back):
  beta = 90 - rafter_angle
  b = back(chord_back) - front(chord_front) + (2 * roof_overhang)
  return b / (math.sin(math.radians(beta)))

def make_rafters(chord_front, chord_back, roof_angle):
  rafter_length = calculate_rafter_length(roof_angle, chord_front, chord_back)

  distance = chord_front.Length.Value
  rafter_space_count = math.ceil(distance/rafter_max_distance)
  rafter_count = rafter_space_count + 1
  rafter_space = (distance - (rafter_count * beam_thickness)) / rafter_space_count

  rafters = []
  for i in range(0, rafter_count):
    rafter = makeCuboid('Rafter' + str(i), beam_thickness, rafter_length, rafter_height)
    offset = (i * rafter_space) + (i * beam_thickness)
    moveLeftFrontBottom(rafter, left(chord_front) + offset, front(chord_front) - roof_overhang, top(chord_front))

    rafters.append(rafter)
  return rafters

def make_battens(rafters, roof_angle):
  batten_length = right(rafters[-1]) - left(rafters[0])

  b = rafter_height
  alpha = roof_angle
  beta = 90 - alpha
  c = b / (math.sin(math.radians(beta)))
  a = math.sqrt(math.pow(c, 2) - math.pow(b, 2))
  back_cutaway = a

  distance = rafters[0].Width.Value - back_cutaway
  batten_space_count = math.ceil(distance/batten_max_distance)
  batten_count = batten_space_count + 1
  batten_space = (distance - (batten_count * batten_thickness)) / batten_space_count

  battens = []
  for i in range(0, batten_count):
    batten = makeCuboid('Batten' + str(i), batten_length, batten_thickness, batten_height)
    offset = (i * batten_space) + (i * batten_thickness)
    moveLeftFrontBottom(batten, left(rafters[0]), front(rafters[0]) + offset, top(rafters[0]))
    battens.append(batten)
  return battens


doc = init_doc()

frame_group = doc.addObject("App::DocumentObjectGroup", "Frame")
roof_group = doc.addObject("App::DocumentObjectGroup", "Roof")
facade_group = doc.addObject("App::DocumentObjectGroup", "Facade")
foundation_group = doc.addObject("App::DocumentObjectGroup", "Foundation")

# 4 corners
#######

stud_front_left = makeStud('StudFrontLeft', height_front)
moveLeftFrontBottom(stud_front_left, 0, 0, 0)

stud_front_right = makeStud('StudFrontRight', height_front)
moveLeftFrontBottom(stud_front_right, shed_width - beam_thickness, 0, 0)

stud_back_left = makeStud('StudBackLeft', height_back - beam_overlap)
moveLeftFrontBottom(stud_back_left, 0, shed_depth - beam_thickness, 0)

stud_back_right = makeStud('StudBackRight', height_back - beam_overlap)
moveLeftFrontBottom(stud_back_right, shed_width - beam_thickness, shed_depth - beam_thickness, 0)

frame_group.addObjects([stud_front_left, stud_front_right, stud_back_left, stud_back_right])

# upper chords
########

chord_front = makeCuboid('ChordFront', x=shed_width + (2 * roof_overhang), y=beam_thickness, z=beam_thickness)
moveLeftFrontBottom(chord_front, left(stud_front_left) - roof_overhang, front(stud_front_left), top(stud_front_left) - beam_overlap)

chord_back = makeCuboid('ChordBack', x=shed_width + (2 * roof_overhang), y=beam_thickness, z=beam_thickness)
moveLeftFrontBottom(chord_back, left(stud_back_left) - roof_overhang, front(stud_back_left), top(stud_back_left))

chord_left = makeCuboid('ChordLeft', x=beam_thickness, y=front(stud_back_left) - back(stud_front_left) + (2 * beam_overlap), z=beam_thickness)
moveLeftFrontBottom(chord_left, left(stud_front_left), back(stud_front_left) - beam_overlap, bottom(chord_back))

chord_right = makeCuboid('ChordRight', x=beam_thickness, y=front(stud_back_right) - back(stud_front_right) + (2 * beam_overlap), z=beam_thickness)
moveLeftFrontBottom(chord_right, left(stud_front_right), back(stud_front_right) - beam_overlap, bottom(chord_back))

frame_group.addObjects([chord_front, chord_back, chord_left, chord_right])

# door
####

stud_door_left = makeStud('StudDoorLeft', height_front)
moveLeftFrontBottom(stud_door_left, (shed_width/2) - (door_width/2) - beam_thickness, 0, 0 )

stud_door_right = makeStud('StudDoorRight', height_front)
moveLeftFrontBottom(stud_door_right, (shed_width/2) + (door_width/2), 0, 0 )

chord_door = makeCuboid('ChordDoor', x=left(stud_door_right)-right(stud_door_left)+(2*beam_overlap), y=beam_thickness, z=beam_thickness)
moveLeftFrontBottom(chord_door, right(stud_door_left)-beam_overlap, front(stud_door_left), door_height) 

frame_group.addObjects([stud_door_left, stud_door_right, chord_door])

# inner studs
##########

inner_studs_left = makeInnerStuds(name='Left', height=height_back, from_stud=stud_front_left, to_stud=stud_back_left, direction='front_to_back')
inner_studs_right = makeInnerStuds(name='Right', height=height_back, from_stud=stud_front_right, to_stud=stud_back_right, direction='front_to_back')
inner_studs_back = makeInnerStuds(name='Back', height=height_back, from_stud=stud_back_left, to_stud=stud_back_right, direction='left_to_right')

frame_group.addObjects(inner_studs_left)
frame_group.addObjects(inner_studs_right)
frame_group.addObjects(inner_studs_back)

# support front
########

support_front_left = makeSupportBeam('FrontLeft', at_stud=stud_door_left, direction='left')
support_front_right = makeSupportBeam('FrontRight', at_stud=stud_door_right, direction='right')

support_back_left = makeSupportBeam('BackLeft', at_stud=inner_studs_back[0], direction='left')
support_back_right = makeSupportBeam('BackRight', at_stud=inner_studs_back[-1], direction='right')

support_left_front = makeSupportBeam('LeftFront', at_stud=inner_studs_left[0], direction='front')
support_left_back = makeSupportBeam('LeftBack', at_stud=inner_studs_left[-1], direction='back')

support_right_front = makeSupportBeam('RightFront', at_stud=inner_studs_right[0], direction='front')
support_right_back = makeSupportBeam('RightBack', at_stud=inner_studs_right[-1], direction='back')

frame_group.addObjects([support_front_left, support_front_right, support_back_left, support_back_right, support_left_front, support_left_back, support_right_front, support_right_back])

# roof
####

roof_angle = calculate_roof_angle(chord_front, chord_back)
rafters = make_rafters(chord_front, chord_back, roof_angle)
roof_group.addObjects(rafters)
battens = make_battens(rafters, roof_angle)
roof_group.addObjects(battens)

Draft.rotate(roof_group.OutListRecursive, angle=roof_angle * -1, axis=FreeCAD.Vector(1, 0, 0), center=FreeCAD.Vector(0, front(chord_front), top(chord_front)))

# facade
#####

def make_facade(name, face, from_stud, to_stud, top=door_height + door_extra_gap, bottom=0, vertical_direction='down', door_gap_side=None):
  height = top - bottom
  last_board_width = height % facade_board_width
  rows = math.ceil(height / facade_board_width)

  if door_gap_side:
    door_gap = door_extra_gap
  else:
    door_gap = 0

  if door_gap_side == 'left':
    door_gap_pos_offset = door_gap
  else:
    door_gap_pos_offset = 0

  if face == 'front':
    x = right(to_stud) - left(from_stud) - door_gap
    y = facade_board_thickness
    pos_x = left(from_stud) + door_gap_pos_offset 
    pos_y = front(from_stud) - facade_board_thickness
  elif face == 'back':
    x = right(to_stud) - left(from_stud)
    y = facade_board_thickness
    pos_x = left(from_stud)
    pos_y = back(from_stud)
  elif face == 'left':
    x = facade_board_thickness
    y = back(to_stud) - front(from_stud)
    pos_x = left(from_stud) - facade_board_thickness 
    pos_y = front(from_stud)
  elif face == 'right':
    x = facade_board_thickness
    y = back(to_stud) - front(from_stud)
    pos_x = right(from_stud)
    pos_y = front(from_stud)
  else:
    raise ValueError('Unknown face: ' +  face)
  
  for i in range(0, rows):
    if vertical_direction == 'down':
      move = moveLeftFrontTop
      pos_z = top - (i * facade_board_width)
    elif vertical_direction == 'up':
      move = moveLeftFrontBottom
      pos_z = bottom + (i * facade_board_width)
    else:
      raise ValueError('Unknown vertical direction: ' +  vertical_direction)
    
    if i == rows - 1:
      z = last_board_width
    else:
      z = facade_board_width

    
    board = makeCuboid(name + str(i+1), x, y, z)
    move(board, pos_x, pos_y, pos_z)
    facade_group.addObject(board)

make_facade('FacadeFrontLeft', 'front', from_stud=stud_front_left, to_stud=stud_door_left, door_gap_side='right')
make_facade('FacadeFrontRight', 'front', from_stud=stud_door_right, to_stud=stud_front_right, door_gap_side='left')
make_facade('FacadeFrontAboveDoor', 'front', from_stud=stud_front_left, to_stud=stud_front_right, top=top(chord_front), bottom=door_height + door_extra_gap, vertical_direction='up')
make_facade('FacadeLeft', 'left', from_stud=stud_front_left, to_stud=stud_back_left)
make_facade('FacadeRight', 'right', from_stud=stud_front_right, to_stud=stud_back_right)
make_facade('FacadeBack', 'back', from_stud=stud_back_left, to_stud=stud_back_right)

all_studs = [stud_front_left, stud_front_right, stud_back_left, stud_back_right, stud_door_left, stud_door_right] + inner_studs_left + inner_studs_right + inner_studs_back
for stud in all_studs:
  cylinder = doc.addObject("Part::Cylinder", stud.Label + "Foundation")
  cylinder.Height = foundation_height
  cylinder.Radius = foundation_diameter / 2
  new_x = left(stud) + (stud.Length.Value / 2)
  new_y = front(stud) + (stud.Width.Value / 2)
  new_z = bottom(stud) - foundation_height - foundation_gap
  Draft.move(cylinder, FreeCAD.Vector(new_x, new_y, new_z))
  foundation_group.addObject(cylinder)

def make_anchor(stud, rotation=0):
  side_a = makeCuboid(stud.Label + 'AnchorSideA', anchor_thickness, anchor_width, anchor_height)
  side_b = makeCuboid(stud.Label + 'AnchorSideB', anchor_thickness, anchor_width, anchor_height)
  x_a = left(stud) - anchor_thickness
  x_b = right(stud)
  y = front(stud) +  ((beam_thickness - anchor_width) / 2)
  z = bottom(stud) - (anchor_height / 2)
  moveLeftFrontBottom(side_a, x_a, y, z)
  moveLeftFrontBottom(side_b, x_b, y, z)

  anchor = doc.addObject("Part::Compound", stud.Label + 'Anchor')
  anchor.Links = [side_a, side_b]

  stud_center_x = left(stud) + ((right(stud) - left(stud)) / 2)
  stud_center_y = front(stud) + ((back(stud) - front(stud)) / 2)

  Draft.rotate(anchor, angle=rotation, axis=FreeCAD.Vector(0, 0, 1), center=FreeCAD.Vector(stud_center_x, stud_center_y, 0))
  foundation_group.addObject(anchor)

  return anchor
  

for stud in [stud_front_left, stud_front_right, stud_back_left, stud_back_right, stud_door_left, stud_door_right] + inner_studs_back:
  make_anchor(stud)

for stud in inner_studs_left + inner_studs_right:
  make_anchor(stud, rotation=90)


doc.recompute()

FreeCADGui.ActiveDocument.ActiveView.viewIsometric()
FreeCADGui.ActiveDocument.ActiveView.fitAll()

def object_dimensions(obj):
  dimensions = [dimension.Value for dimension in [obj.Length, obj.Width, obj.Height]]
  dimensions.sort()
  return 'x'.join(["{:.1f}".format(x) for x in dimensions])

print("")
print("Parts:")
for group in [frame_group, roof_group, facade_group]:
  for obj in group.OutListRecursive:
    print(object_dimensions(obj))
    pass
